FME workspace mapillary_sequence_2_postgisDB.fmw

Parameters:
- URL_MAPILLARY =
- DestDataset_POSTGIS_4 =   # Connection: Choose database connection for writting the sequence features

Writers:
- POSTGIS_1: POSTGIS to $(DestDataset_POSTGIS_4)

Creator
    GEOMTYPE = Geometry Object
    NUM = 1
    CREATED -> AttributeCreator_2
AttributeCreator_2
    ATTR_TABLE:
      SET_TO url = $(URL_MAPILLARY)
      SET_TO next_url = FME_NULL_VALUE
    -> process_mapillary_data
process_mapillary_data: process_json_data
    NEXT_URL = @Value(next_url)
    URL = @Value(url)
    _CREATION_INSTANCE = @Value(_creation_instance)
    -> mly_sequesces (writer POSTGIS_1)
mly_sequesces (writer POSTGIS_1)
    attributes: ogc_fid int4, captured_at varchar(80), coordinateproperties varchar(80), created_at varchar(80), key varchar(80), starred int4, user_key varchar(80), username varchar(80)

FME custom transformer process_json_data

Parameters:
- _CREATION_INSTANCE = @Value(_creation_instance)   # Creation Instance
- URL = @Value(url)   # url
- NEXT_URL = @Value(next_url)   # Next Url

Input (input)
    -> Tester
Tester
    BOOL_OP = OR
    TEST_CLAUSE = TEST next_url ATTRIBUTE_VALUE_NULL ""
    PASSED -> HTTPCaller
    FAILED -> AttributeCopier
AttributeCopier
    ATTR_TABLE = COPY next_url > url
    -> Tester_4
Tester_4
    BOOL_OP = OR
    TEST_CLAUSE = TEST url NOT_ATTRIBUTE_IS_MISSING ""
    PASSED -> HTTPCaller
HTTPCaller
    CONNECTION_TIMEOUT_LENGTH = 60
    ERROR_ATTR = _error
    FOLLOW_REDIRECTS = No
    HTTP_METHOD = GET
    RESPONSE_HEADER_LIST_ATTR = _headers
    SAVE_FILE = Attribute
    STATUS_CODE_ATTR = _http_status_code
    TARGET_ATTR = _response_body
    TARGET_ATTR_ENCODING = utf-8
    TARGET_URL = @Value(url)
    TRANSFER_TIMEOUT_LENGTH = 90
    USE_COOKIES = No
    VERIFY_SSL_CERTIFICATES = No
    -> JSONFragmenter_2
JSONFragmenter_2
    EXPLODE_FORMAT = JSON
    EXTRACT_ATTR = No
    JSON_ATTR = _response_body
    JSON_QUERY = json["features"]
    READ_FROM_FILE = NO
    REJECT_EMPTY_LISTS = YES
    FRAGMENTS -> ListSearcher
ListSearcher
    ATTR_VALUE = Link
    INDEX_ATTR = _list_index
    LIST_ATTR = _headers{}.name
    SEARCH_TYPE = First exact match
    FOUND -> AttributeCreator
AttributeCreator
    ATTR_TABLE = SET_TO Link = @Value(_headers{@Value(_list_index)}.value)
    -> Tester_3
Tester_3
    BOOL_OP = OR
    TEST_CLAUSE = CASE_INSENSITIVE_TEST @Value(Link) CONTAINS rel="next"
    PASSED -> AttributeSplitter
    FAILED -> AttributeKeeper_3
AttributeSplitter
    ATTR_NAME = Link
    DELIMITER = ,
    DROP_EMPTY_PARTS = Yes
    LIST_NAME = _list
    TRIM_OPTION = Both
    -> ListExploder
ListExploder
    ATTR_ACCUM_MODE = Merge List Attributes
    ATTR_CONFLICT_RES = Use List Attribute Values
    INDEX_ATTR = _element_index
    LIST_ATTR = _list{}
    ELEMENTS -> Tester_5
Tester_5
    BOOL_OP = AND
    TEST_CLAUSE = CASE_INSENSITIVE_TEST @Value(_list) CONTAINS rel="next"
    PASSED -> AttributeSplitter_2
AttributeSplitter_2
    ATTR_NAME = _list
    DELIMITER = ;
    DROP_EMPTY_PARTS = Yes
    LIST_NAME = _list_1
    TRIM_OPTION = Both
    -> ListExploder_2
ListExploder_2
    ATTR_ACCUM_MODE = Merge List Attributes
    ATTR_CONFLICT_RES = Use List Attribute Values
    INDEX_ATTR = _element_index_1
    LIST_ATTR = _list_1{}
    ELEMENTS -> Tester_6
Tester_6
    BOOL_OP = AND
    TEST_CLAUSE = CASE_INSENSITIVE_TEST @Value(_list_1) != rel="next"
    PASSED -> AttributeTrimmer
AttributeTrimmer
    SRC_ATTRS = _list_1
    TRIM_CHARS = <
    TRIM_TO_NONE = Yes
    TRIM_TYPE = Both
    -> AttributeTrimmer_2
AttributeTrimmer_2
    SRC_ATTRS = _list_1
    TRIM_CHARS = >
    TRIM_TO_NONE = Yes
    TRIM_TYPE = Both
    -> AttributeKeeper
AttributeKeeper
    KEEP_ATTRS = _list_1,_response_body
    -> AttributeRenamer
AttributeRenamer
    ATTR_TABLE:
      RENAME_SET_DEFAULT _list_1 > next_url
      RENAME_SET_DEFAULT _response_body > body
    -> Caller
AttributeKeeper_3
    KEEP_ATTRS = _response_body
    -> AttributeRenamer_2
AttributeRenamer_2
    ATTR_TABLE = RENAME_SET_DEFAULT _response_body > body
    -> Caller
Caller: JavaScriptCaller
    JSENGINE = CLASSIC
    JSSOURCE = fme_set_attribute("size",JSON.parse(fme_get_attribute("body")).length)
    NEW_ATTRIBUTES = size
    -> JSONFragmenter_3
JSONFragmenter_3
    EXPLODE_FORMAT = JSON
    EXTRACT_ATTR = Yes
    JSON_ATTR = body
    JSON_QUERY = json[*]
    RECURSIVE = Yes
    FRAGMENTS -> JSONExtractor
JSONExtractor
    EXTRACT_QUERY_TABLE = properties json["properties"] geometry json["geometry"]
    JSON_DOCUMENT = @Value(body)
    READ_FROM_FILE = NO
    EVALUATED -> JSONExtractor_2
JSONExtractor_2
    EXTRACT_QUERY_TABLE = coordinateProperties json["coordinateProperties"]
    JSON_DOCUMENT = @Value(properties)
    READ_FROM_FILE = NO
    EVALUATED -> JSONFlattener
JSONFlattener
    ERROR_LIST_ATTR = _json_error
    JSON_DOCUMENT = @Value(properties)
    NEW_ATTRIBUTES = captured_at created_at key starred user_key username
    READ_FROM_FILE = NO
    RECURSIVE = Yes
    -> GeometryReplacer
GeometryReplacer
    ELLIPSOID_NAME = WGS84
    KIND_LONG = GeoJSON
    LETTERING = WGS84
    MSSQL_FORMAT_CHOICE = Geometry
    OGC_WKT_PRECISION_DISPLAY = 64-bit
    OUTPUT_POINT_DISPLAY = Point
    REMOVE_ATTRIBUTE = No
    SOURCE = @Value(geometry)
    SRS_AXIS_ORDER_DISPLAY = Automatic
    -> Reprojector_2
Reprojector_2
    DEST = EPSG:3008
    INTERPOLATION_TYPE_NAME = Nearest Neighbor
    RASTER_CELL_SIZE = Preserve Cells
    RASTER_TOLERANCE = 0.0
    SOURCE = EPSG:4326
    REPROJECTED -> CoordinateSystemSetter
CoordinateSystemSetter
    COORDSYS = EPSG:3008
    -> Tester_2
Tester_2
    BOOL_OP = AND
    TEST_CLAUSE = TEST @Value(json_index) = @sub(@Value(size),1)
    PASSED -> Tester_8
    PASSED -> Output (output)
    FAILED -> Output (output)
Tester_8
    BOOL_OP = OR
    TEST_CLAUSE = TEST next_url NOT_ATTRIBUTE_IS_EMPTY ""
    PASSED -> AttributeKeeper_2
AttributeKeeper_2
    KEEP_ATTRS = next_url
    -> Input (output)
Input (output)
Output (output)
